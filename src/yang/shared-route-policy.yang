module shared-route-policy {

  namespace "http://example.com/shared-route-policy";
  prefix shared-route-policy;

  import ietf-inet-types {
    prefix inet;
  }
  import tailf-common {
    prefix tailf;
  }
  import tailf-ncs {
    prefix ncs;
  }

  description
    "Bla bla...";

  revision 2016-01-01 {
    description
      "Initial revision.";
  }

  list basic-shared-policy {
    key 'device policy';
    leaf device {
      tailf:cli-allow-range;
      type leafref {
        path "/ncs:devices/ncs:device/ncs:name";
      }
    }
    leaf policy {
      tailf:cli-allow-range;
      description "name of route policy";
      type string;
    }

    leaf-list chunk {
      description 'Take care to make sure that all chunks can combine i.e. each chunk should be a self contained rule';
      type string;
      ordered-by user;
    }
    uses ncs:service-data;
    ncs:servicepoint basic-shared-route-policy-servicepoint;
  }

  list shared-route-policy {
    key 'device match';
    leaf device {
      tailf:cli-allow-range;
      type leafref {
        path "/ncs:devices/ncs:device/ncs:name";
      }
    }

    leaf match {
      tailf:info "Community to match";
      tailf:cli-allow-range;
      type string;
    }

    leaf set {
      description "RT to set";
      type string;
      mandatory true;
    }

    uses ncs:service-data;
    ncs:servicepoint shared-route-policy-servicepoint;
  }
}
